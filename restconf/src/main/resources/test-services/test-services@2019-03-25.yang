module test-services {
    yang-version 1.1;
    namespace tests:test-services;
    prefix ts;

    revision "2019-03-25" {
        description
          "Initial revision.";
    }

    container test-data {
        list services {
            key "type-of-com.tencent.sence.adapter.com.tencent.sence.adapter.service";
            leaf type-of-com.tencent.sence.adapter.com.tencent.sence.adapter.service {
                type string;
            }

            list instance {
                key "instance-name";

                leaf instance-name {
                    type string;
                }

                leaf provider {
                    type string;
                }
            }

            container next-data {
                leaf next-com.tencent.sence.adapter.com.tencent.sence.adapter.service {
                    type string;
                }
            }
        }
    }
}
